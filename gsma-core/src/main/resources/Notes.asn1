ExtensionIdentifier ::= OBJECT IDENTIFIER

ExtensionValue ::= CHOICE {
  utf8String   UTF8String,
  integer      INTEGER,
  octets       OCTET STRING,
  boolean      BOOLEAN,
  null         NULL
  -- Add more types as needed based on your actual extension set
}

ManagementExtension ::= SEQUENCE {
  identifier    ExtensionIdentifier,
  significance  [1] IMPLICIT BOOLEAN DEFAULT FALSE,
  information   [2] ExtensionValue
}

DMI-EXTENSION ::= DMI-TYPE-IDENTIFIER

ManagementExtension ::= SEQUENCE {
  identifier    DMI-EXTENSION.&id({ManagementExtensionSet}),
  significance  [1]  BOOLEAN DEFAULT FALSE,
  information
    [2]  DMI-EXTENSION.&Value({ManagementExtensionSet}{@.identifier})
}

ManagementExtensionSet DMI-EXTENSION ::=
  {...}

DMI-TYPE-IDENTIFIER ::= CLASS {
  &id     OBJECT IDENTIFIER UNIQUE,
  &Value
}WITH SYNTAX {TYPE &Value
              ID &id
}
